--
-- MyCC is 'My CallControl protocol',version 2
-- 07.08.2017,Dimitar Kokov
--
-- edit ,09.08.2017 , Dimitar Kokov

MyCC DEFINITIONS ::= BEGIN

MyCC-PDU ::= CHOICE {
	myRequest  [1] MyRequest,
	myResponse [2] MyResponse
}

MyRequest ::= SEQUENCE {
	header  [1] MyHeader,
	payload [2] MyRequestPayload 
}

MyResponse ::= SEQUENCE {
	header  [1]  MyHeader,
	payload [2]  MyResponsePayload
}

MyRequestPayload ::= CHOICE {
	maxsec  [1] MyRequestMaxsec,
	balance [2] MyRequestBalance,
	rate    [3] MyRequestRate,
	term    [4] MyRequestTerm,
	status  [5] NULL
}

MyResponsePayload ::= CHOICE {
	maxsec  [1] MyResponseMaxsec,
	balance [2] MyResponseBalance,
	rate    [3] MyResponseRate,
	term    [4] NULL,
	status  [5] NULL
}

MyRequestMaxsec ::= SEQUENCE {
	callId        [1] MyCall,
	callingNumber [2] MyE164Number,
	calledNumber  [3] MyE164Number	
}

MyRequestBalance ::= SEQUENCE {
	callingNumber MyE164Number
}

MyRequestRate ::= SEQUENCE {
	callingNumber [1] MyE164Number,
	calledNumber  [2] MyE164Number
}

MyRequestTerm ::= SEQUENCE {
	callId        [1] MyCall,
	callingNumber [2] MyE164Number,
	calledNumber  [3] MyE164Number,
	billsec       [4] MyBillSec
}

MyResponseMaxsec ::= SEQUENCE {
	maxsec INTEGER
}

MyResponseBalance ::= SEQUENCE {
	amount NumericString
}

MyResponseRate ::= SEQUENCE {
	cprice NumericString
}

MyHeader ::= SEQUENCE {
	cdrServerId   [1] INTEGER,
	transactionId [2] INTEGER,
	version       [3] INTEGER,
	timestamp     [4] INTEGER,
	hostname      [5] OCTET STRING SIZE(4..32)
}

MyCall ::= SET {
	callId OCTET STRING
}

MyE164Number ::= SET {
	e164 OCTET STRING SIZE(11..32)
}

MyBillSec ::= SET {
	billsec INTEGER
}

END
